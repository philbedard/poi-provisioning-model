module poi-l1circuit {
    yang-version 1.1;
    namespace "urn:ietf:params:xml:ns:yang:ietf-l2vpn-ntw";
    prefix l1circuit-ntw;

    import ietf-inet-types {
        prefix inet;
        reference
        "RFC 6991: Common YANG Data Types, Section 4";
    }
    import ietf-yang-types {
        prefix yang;
        reference
        "RFC 6991: Common YANG Data Types, Section 3";
    }

    organization
        "IETF ACTN (Action and Control of Traffic Engineering Networks) Working Group";
    contact
        "WG Web:   <https://datatracker.ietf.org/wg/actn/>
        WG List:  <mailto:actn@ietf.org>

        Editor:    Phil Bedard 
                <mailto:phbedard@cisco.com>"; 



    description
        "This YANG module defines a network model for Layer 1 Optical
        Services.

        Copyright (c) 2023 IETF Trust and the persons identified as
        authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).

        This version of this YANG module is part of RFC 9291; see
        the RFC itself for full legal notices.";

    revision 2023-08-29 {
        description
        "Initial version.";
    }



/* Identities */ 

/* TBD */ 

    typedef service-id-type {
        type string;
        description 
            "Defines the service ID to uniquely identify each service"; 
    }

    typedef frequency-type {
        type uint64; 
        units "MHz"; 
        description 
            "Optical spectrum frequency in MHz, Example: 194.30 THz would be expressed as 194300000";   
        }
    
    typedef plug-id-type { 
        type string;
        description 
            "Plug-ID used to identify port when used as part of an inter-domain link. Example: Router pluggable connected to OLS ROADM add/drop port";  
    }
    
    identity modulation-types {
        description 
            "Base identity for modulation types"; 
        }
    
    identity MODULATION_QPSK {
        base modulation-types;  
        description 
            "QPSK modulation type for optical configuration";  
        }
    
    identity MODULATION_8QAM {
        base modulation-types;  
        description 
            "8QAM modulation type for optical configuration";  
        }
    
    identity MODULATION_16QAM { 
        base modulation-types;  
        description 
            "16QAM modulation type for optical configuration";  
        }
    
    identity line-port-rate-type {
        description 
            "Base identity for support rates"; 
        }
    
    identity rate-type_800G { 
        base line-port-rate-type; 
    }

    identity rate-type_400G { 
        base line-port-rate-type; 
    }
    
    identity rate-type_100G { 
        base line-port-rate-type; 
    }
    
    identity rate-type_200G { 
        base line-port-rate-type; 
    }
    
    identity rate-type_300G { 
        base line-port-rate-type; 
    }
    
    identity rate-type_500G { 
        base line-port-rate-type; 
    }
    
    identity rate-type_600G { 
        base line-port-rate-type; 
    }
    
    identity rate-type_700G { 
        base line-port-rate-type; 
    }

    identity host-port-channels-type { 
        description 
            "Identities to support transponder or muxponder applications where the number of channels on the host electrical side of the port"; 
    }
    
    identity CHANNELS_1 { 
        base host-port-channels-type; 
    }
    identity channels-type_2 { 
        base host-port-channels-type; 
    }
    identity channels-type_3 { 
        base host-port-channels-type; 
    }
    identity channels-type_4 { 
        base host-port-channels-type; 
    }
    identity channels-type_5 { 
        base host-port-channels-type; 
    }
    identity channels-type_6 { 
        base host-port-channels-type; 
    }
    identity channels-type_7 { 
        base host-port-channels-type; 
    }
    identity channels-type_8 { 
        base host-port-channels-type; 
    }

    identity fec-types {
        description 
            "Base identity for modulation types"; 
        }
    
    identity CFEC {
        base fec-types;  
        description 
            "Concatenated FEC type"; 
        reference 
            "Insert OIF reference"; 
        }
    
    identity OFEC {
    base fec-types;  
        description 
            "OpenROADM FEC type"; 
        reference 
            "Insert OpenROADM reference"; 
        }

    identity framing-types {
        description 
            "Base identity for modulation types"; 
        }
    
    identity ETHERNET {
        base fec-types;  
        description 
            "Ethernet Framing"; 
        reference 
            "Insert ZR400 reference"; 
        }
    
    identity OTN {
        base fec-types;  
        description 
            "OTN Framing"; 
        reference 
            "Insert ITU-T reference"; 
        }


    typedef admin-state-type {
        description 
        "The possible values of the administrative state.";
        type enumeration {
            enum LOCKED {
                description "Users are administratively prohibited from making use of the resource.";
            }
            enum UNLOCKED {
                description "Users are allowed to use the resource";
            }
            enum MAINTENANCE {
                description "Resource is in maintenance state";
            }
        }
    } 
    

    grouping administrative-state {
        description 
            "Configures the administrative state of the resource";  
        leaf admin-state { 
            type admin-state-type; 
        }
    } 
    grouping standard-operational-mode { 
        leaf operational-mode { 
            description
                "Standards-based operational mode"; 
            type string;  
        } 
    }   
    grouping organizational-operational-mode {
        leaf organization-identifier { 
            description 
                "Prefix to operational mode speciic to an organization or standard";  
            type string;
        }
        leaf operational-identifier { 
            description 
                "Identifies the operational mode of the optics, must be identical on each end of the circuit"; 
            type string;
        }
    }

    grouping explicit-optical-configuration {
        description  
            "Explicit configuration for optical parameters typically defined by the operational mode. If both the operational-mode and explicit configuration are supplied, the explicit configuration will override the default setting expresed by the operatinal-mode"; 
        container explicit-optical-configuration {
            description 
                "Physical layer optical configuration parameters"; 
            leaf symbol-rate { 
                description 
                    "Symbol rate or baud rate (symbols/sec) in MBaud. Example 60.1Gbaud = 60100000";
                type uint32;
                units MBd;  
            } 
            leaf host-channels { 
                description 
                    "Number of channels to multiplex into line side trunk. Examples: 4x100G, 2x100G, 1x400G, 1x100G"; 
                type identityref { 
                    base host-port-channels-type; 
                }
            }
            leaf port-rate { 
                description 
                    "Line side trunk rate"; 
                type identityref { 
                    base line-port-rate-type; 
                }
            }
            leaf modulation { 
                description 
                    "Optical modulation EG: QPSK, 8QAM, 16QAM"; 
                type identityref { 
                    base modulation-types; 
                }
            }
            leaf fec-type { 
                description 
                    "Forward Error Correction type"; 
                type identityref { 
                    base fec-types;  
                }
            }
            /* Not sure there is a standard way to express this as it could mean on, off, or a specific type of shaping (RRC, RC) */ 
            leaf pulse-shaping { 
                description
                    "Defines if pulse-shaping is used on the transmit signal";
                type enumeration { 
                    enum ON { 
                        description 
                            "Enable pulse shaping on transmit signal"; 
                    }
                    enum OFF { 
                        description 
                            "Disable pulse shaping"; 
                    }
                }
                default OFF; 
            } 
        }

    }

/* 
    grouping optical-power-config {
        leaf target-output-power {
            description 
                "Transmit (TX) power value expressed in increments of .01 dBm. Example: Output power 1.50 would be expressed as 150";  
            type uint16; 
            units dBm; 
        }
    } 

*/ 

    grouping optical-frequency-config {
        leaf central-frequency {
            description 
                "Optical spectrum frequency expressed in Mhz"; 
            type frequency-type;  
        }
    } 
        
    grouping optical-service-common-config { 
        description 
            "Common circuit administrative properties";
        uses administrative-state;  
        leaf circuit-name {
            description 
                "Descriptive name for the service";  
            type string; 
        }
        leaf circuit-description {
            description 
                "Longer description of the circuit, can be used for additional meta-data associated with the circuit"; 
            type string; 
        }
        leaf customer-name {
            description 
                "Customer associated with the circuit";  
            type string; 
        }
    }
    

    grouping optical-parameter-config {
        description
            "Contains all optical paramter configuration"; 
        uses explicit-optical-configuration; 
        uses optical-frequency-config;   
    } 
    

    grouping optical-service-global-configuration { 
        description 
            "Global optical parameter configuration used by subsequent optical endpoints";

        uses optical-parameter-config; 
    }

/* Use container or no? */ 
    grouping node-optical-configuration { 
        description 
            "Node specific optical parameter configuration"; 
        container node-configuration { 
            leaf description {
                description 
                    "Description of the node";  
                type string;  
            }
            leaf node-id { 
            description 
                "Identified circuit endpoint node, in POI typically a router name"; 
            type string; 
            mandatory true; 
            }
        } 
    }

    grouping interface-lag-configuration { 
        description
            "Configuration specific to managing node service interfaces part of an Ethernet LAG"; 
            container lag-interface-config { 
                leaf lag-interface-id { 
                    description "Identifies LAG interface on node";
                    type string;  
                }
            }
    }


   grouping interface-srlg-configuration { 
        description 
            "Configuration related to application of SRLG data to node interfaces"; 
        container srlg { 
             
        }
   }

/*  Probably best to not get into the weeds of IP address config in this model  
   grouping interface-ip-configuration { 
        description 
            "IP interface address configuration"; 
        container ip-config {
            leaf address-ipv4 { 
                description 
                    "IPv4 address assigned to the host Ethernet interface"; 
                type inet:ipv4-address; 
            }
            leaf address-ipv6 { 
                description 
                    "IPv6 address assigned to the host Ethernet interface"; 
                type inet:ipv6-address; 
            }
        }
   }
*/

    grouping port-optical-configuration { 
        description 
            "Port specific optical parameter configuration"; 
        container port-optical-configuration {
            leaf port-id {
                description 
                    "Unique port identifier";  
                type string; 
                mandatory true; 
            }
            leaf description {
                description 
                    "Port description, can be applied as description to the device port";  
                type string;  
            }
            leaf target-output-power {
                description 
                    "Transmit (TX) power value expressed in increments of .01 dBm. Example: Output power 1.50 would be expressed as 150";  
                type uint16; 
                units dBm; 
            }
            leaf node-port-id {   /* Should align to optical-impairment draft */  
                description
                    "String identifying the hardware port to be configured on the node"; 
                type string;
                mandatory true;  
            }
            leaf local-plug-id {  /* align to TAPI? */  
                description
                    "Identifier for local plug-id in inter-domain link";
                type plug-id-type;  
            }
            leaf remote-plug-id {  /* align to TAPI? */  
                description
                    "Identifier for remote plug-id in inter-domain link, administrative use only";
                type plug-id-type;  
            }
            leaf cd-range-min { 
                description 
                    "Minimum range for chromatic dispersion compensation expressed in ps/nm-km";
                type uint32; 
            } 
            leaf cd-range-max { 
                description 
                    "Maximum range for chromatic dispersion compensation expressed in ps/nm-km"; 
                type uint32; 
            }

        }
    }      

    grouping port-packet-configuration {
        description 
            "Packet layer configuration for host interfaces"; 
        container port-packet-configuration { 
            description 
                "Container for all packet layer configuration on host interface"; 
            uses interface-lag-configuration; 
        } 
               
    }

  /* Main Container */  
    container l1nm-ntw { 
        description 
            "Main container for L1 circuit network services";     
        container "l1nm-services" { 
            list l1nm-service {
                leaf service-id { 
                    type service-id-type;
                    mandatory true;  
                }
                key "service-id";

            container global-parameters { 
                uses optical-service-common-config; 
                uses optical-service-global-configuration;
                choice operational-mode-config { 
                    description
                        "The integer operational mode sets several optical parameters using a single value, simplifying discovery and configuration. The operational mode can either be standards based or defined by an organization"; 
                        case organization-defined {
                            description 
                                "An organization proprietary mode is used";  
                            uses organizational-operational-mode;  
                        } 
                        case standard-defined { 
                            description
                                "A standards-based mode is used";
                            leaf operational-mode {
                                type uint16; 
                            }
                        }
                
                } 
            }
            container optical-service-nodes { 
                description 
                    "Set of nodes terminating an optical service. Minimum 1, Maximum 2";
                list optical-service-node {
                    min-elements 1; 
                    max-elements 2;  
                    key "node-id";
                    leaf node-id { 
                        type leafref { 
                            path "../node-configuration/node-id"; 
                        }
                    }
                    uses node-optical-configuration;  
                    uses port-optical-configuration; 
                    uses port-packet-configuration;   
                }
            }
                 
            
        }
    }
    
    }
}
