module poi-l1nm-combined {
    yang-version 1.1;
    namespace "urn:ietf:params:xml:ns:yang:ietf-l2vpn-ntw";
    prefix l1circuit-ntw;

/*
    import ietf-inet-types {
        prefix inet;
        reference
        "RFC 6991: Common YANG Data Types, Section 4";
    }
    import ietf-yang-types {
        prefix yang;
        reference
        "RFC 6991: Common YANG Data Types, Section 3";
    }

*/
    organization
        "IETF ACTN (Action and Control of Traffic Engineering Networks) Working Group";
    contact
        "WG Web:   <https://datatracker.ietf.org/wg/actn/>
        WG List:  <mailto:actn@ietf.org>

        Editor:    Phil Bedard 
                <mailto:phbedard@cisco.com>

        Editor:    Prasenjit Manna  
                <mailto:samier.barguilgiraldo.ext@telefonica.com>"; 


    description
        "This YANG module defines a network model for Layer 1 Optical
        Services.

        Copyright (c) 2023 IETF Trust and the persons identified as
        authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).

        This version of this YANG module is part of RFC 9291; see
        the RFC itself for full legal notices.";

    revision 2023-08-29 {
        description
        "Initial version.";
    }



/* Identities */ 

/* TBD */ 

    typedef circuit-id-type {
        type string;
        description 
            "Defines the circuit ID to unique identify each service"; 
    }

    typedef frequency-type {
        type uint64; 
        units "MHz"; 
        description 
            "Optical spectrum frequency in MHz, Example: 194.30 THz would be expressed as 194300000";   
        }
    
    identity modulation-types {
        description 
            "Base identity for modulation types"; 
        }
    
    identity QPSK {
        base modulation-types;  
        description 
            "QPSK modulation type for optical configuration";  
        }
    
    identity QAM8 {
        base modulation-types;  
        description 
            "8QAM modulation type for optical configuration";  
        }
    
    identity QAM16 { 
        base modulation-types;  
        description 
            "16QAM modulation type for optical configuration";  
        }
    
    identity fec-types {
        description 
            "Base identity for modulation types"; 
        }
    
    identity CFEC {
        base fec-types;  
        description 
            "Concatenated FEC type"; 
        reference 
            "Insert OIF reference"; 
        }
    
    identity OFEC {
    base fec-types;  
        description 
            "OpenROADM FEC type"; 
        reference 
            "Insert OpenROADM reference"; 
        }

    identity framing-types {
        description 
            "Base identity for modulation types"; 
        }
    
    identity ETHERNET {
        base fec-types;  
        description 
            "Ethernet Framing"; 
        reference 
            "Insert ZR400 reference"; 
        }
    
    identity OTN {
        base fec-types;  
        description 
            "OTN Framing"; 
        reference 
            "Insert ITU-T reference"; 
        }
    
    identity admin-state { 
        description 
            "Administrative state of the circuit"; 
    } 
    
    identity UNLOCKED {
        base admin-state;  
        description 
            "Unlocked admin state means the circuit is considered to be in-service (admin up)"; 
    } 
    
    identity MAINTENANCE {
        base admin-state;  
        description 
            "Circuit is currently in maintenance state and out of service"; 
    } 
    
    identity LOCKED {
        base admin-state;  
        description 
            "Circuit is currently out of service (admin down)"; 
    } 
    grouping standard-operational-mode { 
        leaf operational-mode { 
            description
                "Standards-based operational mode"; 
            type string;  
        } 
    }   
    grouping organizational-operational-mode {
        leaf organization-identifier { 
            description 
                "Prefix to operational mode speciic to an organization or standard";  
            type string;
        }
        leaf operational-identifier { 
            description 
                "Identifies the operational mode of the optics, must be identical on each end of the circuit"; 
            type string;
        }
    }

    grouping explicit-optical-configuration {
        description  
            "Explicit configuration for optical parameters typically defined by the operational mode. If both the operational-mode and explicit configuration are supplied, the explicit configuration will override the default setting expresed by the operatinal-mode"; 
        container explicit-optical-configuration {
            description 
                "Physical layer optical configuration parameters"; 
            leaf symbol-rate { 
                description 
                    "Symbol rate or baud rate (symbols/sec) in MBaud. Example 60.1Gbaud = 60100000";
                type uint32;
                units MBd;  
            } 
            leaf modulation-type { 
                description 
                    "Optical modulation EG: QPSK, 8QAM, 16QAM"; 
                type identityref { 
                    base modulation-types; 
                }
            }
            leaf fec-type { 
                description 
                    "Forward Error Correction type"; 
                type identityref { 
                    base fec-types;  
                }
            }
            /* Not sure there is a standard way to express this as it could mean on, off, or a specific type of shaping (RRC, RC) */ 
            leaf pulse-shaping { 
                description
                    "Defines if pulse-shaping is used on the transmit signal";
                type enumeration { 
                    enum ON { 
                        description 
                            "Enable pulse shaping on transmit signal"; 
                    }
                    enum OFF { 
                        description 
                            "Disable pulse shaping"; 
                    }
                }
                default OFF; 
            } 
        }

    }

/* 
    grouping optical-power-config {
        leaf target-output-power {
            description 
                "Transmit (TX) power value expressed in increments of .01 dBm. Example: Output power 1.50 would be expressed as 150";  
            type uint16; 
            units dBm; 
        }
    } 

*/ 

    grouping optical-frequency-config {
        leaf central-frequency {
            description 
                "Optical spectrum frequency expressed in Mhz"; 
            type frequency-type;  
        }
    } 
        
    grouping optical-service-common-config { 
        description 
            "Common circuit administrative properties"; 
        leaf circuit-name {
            description 
                "Descriptive name for the service";  
            type string; 
        }
        leaf circuit-description {
            description 
                "Longer description of the circuit, can be used for additional meta-data associated with the circuit"; 
            type string; 
        }
        leaf customer-name {
            description 
                "Customer associated with the circuit";  
            type string; 
        }
    }
    

    grouping optical-parameter-config {
        description
            "Contains all optical paramter configuration"; 
        uses explicit-optical-configuration; 
        uses optical-frequency-config;   
    } 
    

    grouping optical-service-global-configuration { 
        description 
            "Global optical parameter configuration used by subsequent optical endpoints";

        uses optical-parameter-config; 
    }

/* Use container or no? */ 
    grouping optical-service-node-configuration { 
        description 
            "Node specific optical parameter configuration"; 
        container node-configuration { 
            leaf description {
                description 
                    "Description of the node";  
                type string;  
            }
            leaf node-id { 
            description 
                "Identified circuit endpoint node, in POI typically a router name"; 
            type string; 
            }
        } 
    }
    
/* Use container or no? */ 
    grouping optical-service-port-configuration { 
        description 
            "Port specific optical parameter configuration"; 
        container port-configuration {
            leaf description {
                description 
                    "Port description, can be applied as description to the device port";  
                type string;  
            }
            leaf target-output-power {
                description 
                    "Transmit (TX) power value expressed in increments of .01 dBm. Example: Output power 1.50 would be expressed as 150";  
                type uint16; 
                units dBm; 
            }
            leaf port-id {   /* Should align to optical-impairment draft */  
                description
                    "String identifying the port to be configured"; 
                type string; 
            }
            leaf cd-range-min { 
                description 
                    "Minimum range for chromatic dispersion compensation expressed in ps/nm-km";
                type uint32; 
            } 
            leaf cd-range-max { 
                description 
                    "Maximum range for chromatic dispersion compensation expressed in ps/nm-km"; 
                type uint32; 
            } 

        }
    }      


  /* Main Container */  
    container l1nm-ntw { 
        description 
            "Main container for L1 circuit network services";     
        container "l1nm-services" { 
            list l1nm-service {
                leaf circuit-id { 
                    type circuit-id-type; 
                }
                key "circuit-id";

            container global-parameters { 
                uses optical-service-common-config; 
                uses optical-service-global-configuration;
                choice operational-mode-config { 
                    description
                        "The integer operational mode sets several optical parameters using a single value, simplifying discovery and configuration. The operational mode can either be standards based or defined by an organization"; 
                        case organization-defined {
                            description 
                                "An organization proprietary mode is used";  
                            uses organizational-operational-mode;  
                        } 
                        case standard-defined { 
                            description
                                "A standards-based mode is used";
                            leaf operational-mode {
                                type uint16; 
                            }
                        }
                
                } 
            }
            container optical-service-nodes { 
                description 
                    "Set of nodes terminating an optical service. Minimum 1, Maximum 2";
                list optical-service-node {
                    max-elements 2;  
                    key "node-id";
                    leaf node-id { 
                        type leafref { 
                            path "../node-configuration/node-id"; 
                        }
                    }
                    uses optical-service-node-configuration;  
                    uses optical-service-port-configuration;  
                }
            } 
            
        }
    }
    
    }
}
